Attribute VB_Name = "Module_des_variables"
'=============================================================== Module des Variables ===============================================================
'Ce Sub contient toutes les variables globales utilisees dans les differents modules, range ici pour plus de clarte





'Variables lies a Update des Parts

Public frontCoords As Variant      ' coords des points du train avant
Public rearCoords As Variant       ' coords des points du train arriere
Public frontNames As Variant       ' liste des noms des points du train avant
Public rearNames As Variant        ' liste des noms des points du train arriere


'Variables lies a l'Userform

Public pathLotus As String
Public pathWireframe As String
Public update_products() As Variant          'tableau qui contiendra les listes de path à mettre à jour
Public update_val As Integer       'cela permettra d'ecrire ou non le nouveau Path des fichiers préselectionnés dans params.txt
Public nb_ligne_update As Integer  'entier permettant d'avoir un nombre variable de produits a ajouter

Attribute VB_Name = "UserForm1"
Attribute VB_Base = "0{26004312-84FA-4C13-AA8E-D376879D7C31}{B69831A0-1595-4BEF-B476-F96014E59924}"
Attribute VB_GlobalNameSpace = False
Attribute VB_Creatable = False
Attribute VB_PredeclaredId = True
Attribute VB_Exposed = False
Attribute VB_TemplateDerived = False
Attribute VB_Customizable = False
Private Sub Add_Products_Click()
    path_variable = CATIA.FileSelectionBox("Select Product File", "*.CATProduct", 0)
    MsgBox path_variable
    MsgBox VarType(path_variable)
    MsgBox Len(path_variable)
    If Len(path_variable) > 1 Then
    'ce if permet de gerer le cas ou l'utilisateur clique sur Add, et finalement clique sur annuler dans l'explorateur de fichiers
    'path_variable contient donc une adresse vide (verifie a laide de Msgbox), et nous ne voulons pas l'ajouter dans update_product
        
        ReDim Preserve update_products(nb_ligne_update)
        update_products(nb_ligne_update) = path_variable  ' on ajoute a la liste  updtaproduct pour faire une MAJ de params a la fin
        Dim split_path_variable() As String
        split_path_variable = Split(path_variable, "\")  'permet de ne recuperer que le nom du CATProduct, plus clair pour l'utilisateur
        ListBox_Products.AddItem (split_path_variable(UBound(split_path_variable)))   'on ajoute a la ListBox
        nb_ligne_update = nb_ligne_update + 1    'la position de cette incrementation est tricky, suite a 2-3 debuggage. Lien avec la boucle For de
                                                    'Userform Activate et la boucle de queryclose
    End If

End Sub

Private Sub Image1_BeforeDragOver(ByVal Cancel As MSForms.ReturnBoolean, ByVal Data As MSForms.DataObject, ByVal X As Single, ByVal Y As Single, ByVal DragState As MSForms.fmDragState, ByVal Effect As MSForms.ReturnEffect, ByVal Shift As Integer)

End Sub

Private Sub Lotus_Click()

End Sub

Private Sub Remove_Products_Click()
    'MsgBox VarType(ListBox_Products.ListCount)
    For i = 0 To ListBox_Products.ListCount - 1
    '    MsgBox ListBox_Products.Selected(i)
        If ListBox_Products.Selected(i) Then
            'MsgBox update_products(i)
            deleteitem update_products, i
            nb_ligne_update = nb_ligne_update - 1
            ListBox_Products.RemoveItem (i)
        End If
    Next i
    
    'j'ai cherhce sur des Forums, il n'existe pas de manière plus simple : on ne peut supprimer que les elements dit selectionne,
    ' et pour les retrouver,on ne peut voir s'il est selectionne qu'en regardant tous les items et en testant .Selected == True
    ' ainsi, il est possible de programmer du Multiselect pour Remove plusisues membre a la fois, et notre structure de code fonctionnerait
    'mais pas très pertinent, pas bcp de membres à remove

End Sub


Private Sub Open_Lotus_Click()
    pathLotus = CATIA.FileSelectionBox("Select Lotus File", "*.dat", 0)
    Lotus_text.Value = pathLotus
End Sub

Private Sub Open_Wireframe_Click()
    pathWireframe = CATIA.FileSelectionBox("Select Wireframe definition Product", "*.CATProduct", 0)
    Wireframe_text.Value = pathWireframe
End Sub

Private Sub Other_Products_Click()

End Sub
Private Sub update_button_Click()
    Call Lect_Lotus
    Call Maj_Catia
    update_val = 1
    MsgBox "updaté!"
    'MsgBox pathWireframe
End Sub

Private Sub UserForm_Activate()
    'ouverture du fichier des parametres pour les valeurs de la macro
    ' obtenir le path de la macro courante
    Set apc = CreateObject("MSAPC.Apc")
    Dim path1 As String
    path1 = apc.VBE.ActiveVBProject.FileName
    Set fs = CreateObject("Scripting.FileSystemObject")
    
    ' le fichier des parametres se trouve dans le meme dossier que la macro
    Dim f As Object
    Set f = fs.GetFile(fs.GetParentFolderName(path1) & "\params.txt")
    Dim ts As Object
    
    'lecture du fichier
    Set ts = f.OpenAsTextStream(ForReading)
    
    ' maj variables globales avec les vieux path
    pathWireframe = ts.ReadLine
    pathLotus = ts.ReadLine
    
    ' affichage vieux path dans le champs dediés
    Wireframe_text.Value = pathWireframe
    Lotus_text.Value = pathLotus
    
    'on recupere les products qui avaient ete update la fois d'avant, et on ajoute dans la ListBox Update Product
    nb_ligne_update = 0
    Do While ts.AtEndOfStream <> True
        ReDim Preserve update_products(nb_ligne_update) 'on redimensionne le tableau en preservant les valeurs d'avant
        update_products(nb_ligne_update) = ts.ReadLine  'on ajoute la ligne
        Dim split_path_variable() As String
        split_path_variable = Split(update_products(nb_ligne_update), "\")  'permet de ne recuperer que le nom du CATProduct
        'MsgBox update_products(nb_ligne_update)
        ListBox_Products.AddItem (split_path_variable(UBound(split_path_variable)))
        nb_ligne_update = nb_ligne_update + 1
    Loop
    
    'initialisation de update_val a 0, permettant de savoir si l'utilisateur a appuie sur le bouton Update et de generer differentes decisions
    update_val = 0
    
    
    'fermeture du fichier ts
    ts.Close

End Sub
Private Sub UserForm_QueryClose(Cancel As Integer, CloseMode As Integer)


    'UserForm_Terminate est la toute toute derniere action, donc cela ne sert a rien de coder a linterieur
    'QueryClose est celle juste avant, et on peut incorporer des actions entre _QueryClose et _Terminate
    'CloseMode permet de savoir comment le Userform a ete ferme (TaskManager, croix Windows etc) : 0 est croix Windows
    'Cette ecriture avec Cancel et Closemode est celle de base, et Cancel permet de retarder la fermeture de la fenetre
    
    If CloseMode = 0 And update_val = 1 Then
            Cancel = True
                'ouverture du fichier des parametres pour les valeurs de la macro
            ' obtenir le path de la macro courante
            Set apc = CreateObject("MSAPC.Apc")
            Dim path2 As String
            path2 = apc.VBE.ActiveVBProject.FileName
            Set fs = CreateObject("Scripting.FileSystemObject")
    
            ' le fichier des parametres se trouve dans le meme dossier que la macro
            Dim f2 As Object
            Set f2 = fs.GetFile(fs.GetParentFolderName(path2) & "\params.txt")
            Dim ts2 As Object
    
            'ecriture du fichier
            Set ts2 = f2.OpenAsTextStream(ForWriting)
            
            
            ts2.WriteLine (pathWireframe)
            ts2.WriteLine (pathLotus)
            
            For i = 0 To nb_ligne_update - 1:
                ts2.WriteLine (update_products(i))              'dans le cas ou updateLotus est sense etre vide, cela ne redige rien donc tant mieux
                MsgBox (update_products(i))                     ' a surveiller, car Update Lotus n'est pas vide, il contient False
            Next                                                ' voir si cela va gener quand on va update
    
            ts2.Close

            
        
            'MsgBox "onferme"
            Cancel = False
    End If
End Sub

Sub deleteitem(table As Variant, index As Variant)
    'cette fonction va permettre de supprimer un element d'un table
    'il n'y a pas de fonction permettant d'enlever simplement un item et de redimensionner
    'donc le but va etre de decaler d'un cran tout les item a partir du rang i, et de Redim Preserve
    
    Dim lentghtable As Integer
    lengthtable = UBound(table)
    If lengthtable = 0 Then
        table(0) = False
    Else
        For j = index To lenghtable
            table(j) = table(j + 1)
        Next j
        ReDim Preserve table(lengthtable - 1)
    End If
    
End Sub

Private Sub Wireframe_text_Change()

End Sub

Attribute VB_Name = "lectureLotus"
'======================================================== Sub LECTURE LOTUS ==========================================================================
'Ce module a pour but de traiter integralement le fichier txt genere par Lotus, contenant toutes les informations utiles de la liaison au sol
'Ce Sub va donc lire le fichier txt et preparer les listes de points proprement pour la mise a jour


Option Compare Text


Sub Lect_Lotus()
'Dim file_name As String         ' path du fichier .dat Lotus
Dim train As Integer            ' 0= avant, 1= arriere
train = 0
Dim fs As FileSystemObject      ' Fyle system obect pour acceder au filesystem
Dim f As Object                 ' objet File pour acceder au fichier Lotus
Dim ts As Object                ' objet TextStream pour lire le fchier Lotus
Dim ln As String                ' variable de ligne pour lire la ligne e l'analyser



    ' open Lotus file by selection
    'Open_Lotus = CATIA.FileSelectionBox("Select Lotus File", "*.dat", 0)
    
    ' ouverture du fichier Lotus
    Set fs = CreateObject("Scripting.FileSystemObject")
    Set f = fs.GetFile(pathLotus)
    Set ts = f.OpenAsTextStream(ForReading)

    ' boucle de lecture ligne
    Do While Not ts.AtEndOfStream
        'lecture ligne courante
        ln = ts.ReadLine
        'MsgBox ln
    
        ' detection des section par mot clef
        If StrComp(ln, "TEMP_SETTINGS", vbTextCompare) = 0 And train = 0 Then
            frontNames = ReadTempSettings(ts)
            train = train + 1
            
        ElseIf StrComp(ln, "TEMP_SETTINGS", vbTextCompare) = 0 And train = 1 Then
          rearNames = ReadTempSettings(ts)
    
       ElseIf StrComp(ln, "FRONT SUSPENSION", vbTextCompare) = 0 And train = 1 Then
         ' lire un nb de poin egal à la taille de la liste des noms
         frontCoords = ReadSuspension(ts, UBound(frontNames) + 1)
            
        ElseIf StrComp(ln, "REAR SUSPENSION", vbTextCompare) = 0 And train = 1 Then
         'lire un nb de poin egal à la taille de la liste des noms
         rearCoords = ReadSuspension(ts, UBound(rearNames) + 1)
      End If
    
    Loop
    ts.Close

    ' log et verification
    MsgBox frontCoords(0, 1)
End Sub


Function ReadTempSettings(ts As Object) As Variant
' lecture des noms de points depuis le TextStream ts, renvoye la liste des noms lus
    Dim i As Integer               'invariant de boucle
    Dim j As Integer
    Dim namepoint As String        ' variable muette pour affectation de Tempsettings
    Dim numpoint As Integer         ' variable qui contiendra la ligne contenant le nombre de points existants
    Dim pointNames() As String      'Dynamic Array definition --> ReDim
    Dim currentline As Variant
    Dim skippart As Integer
    
    With ts
            'On considere que lon a deja lu temp setting, donc on est ligne 1
            ' le deux premieres lignes defnissent le type de template Lotus
            .SkipLine
            .SkipLine
            
            ' la premiere ligne conient le nombre de parts et de points
            currentline = Split(.ReadLine, "          ")
            skippart = CInt(currentline(1))
            numpoint = CInt(currentline(2))
            
            ' definir la dimension de la liste des noms avant de pouvoir la remplir
            ReDim pointNames(numpoint - 1) ' start from 0 index
            
            'sauter le nombre de ligne correspondant au nombre de Part defini par Lotus
            For j = 1 To skippart
            .SkipLine
            Next
            
            ' lecture des noms des points
            i = 0
            Do While i < numpoint
                ' lecture du nom du point
                pointNames(i) = .ReadLine
                'MsgBox pointNames(i)
                i = i + 1
                ' aller au point suivant
                For j = 1 To 8
                    .SkipLine
                Next
            Loop
            
     End With
     ' return the list to the function
     ReadTempSettings = pointNames
End Function


Function ReadSuspension(ts As Object, numpoint As Long) As Variant
' lecture de numpoint lignes dans TextStream ts, renvoye la matrice des coords
    Dim pointCoord() As Double
    ReDim pointCoords(numpoint - 1, 3 - 1)
    
    Dim point As Variant    ' variable pour la conversion de ligne -> coords
    Dim i As Integer        ' variable boucle nb de points
    Dim locale As String    ' variable pour la conversion du separateur decimal
    
    With ts
        'On considere que lon a deja lu temp setting, donc on est ligne 1
        ' la premiere ligne definit le nb du template
        .SkipLine
        i = 0
        Do While i <= numpoint - 1
            ' lecture de la ligne
            locale = LTrim(.ReadLine)
            ' conversion du separateur "." en "," pour le locale FR, IT de l'ordinateur
            locale = Replace(locale, ".", ",")
            point = Split(locale, "            ") ' 12 blancs
            ' enregistrement des cordonnees, conversion str -> double
            pointCoords(i, 0) = CDbl(point(0))
            pointCoords(i, 1) = CDbl(point(1))
            pointCoords(i, 2) = CDbl(point(2))
            i = i + 1
        Loop
    End With
    
    ReadSuspension = pointCoords
End Function

Attribute VB_Name = "majCatia"
'=========================================== Sub MAJ CATIA =======================================================================================
' Ce module a pour but de traiter toutes les requetes lies a l'utilisation de Catia. C'est ce module qui va etre appele pour gerer toute la gestion
' de mise a jour des points

Sub Maj_Catia()
    Dim i As Integer
    'Dim file_name As String
    ' frontNames test pour tester le fonctionnement de la macro
    'Dim frontNames(0 To 2) As String
    'frontNames(0) = "point name 1"
    'frontNames(1) = "point name 2"
    'frontNames(2) = "point name 4"
    
    Dim docs As Documents
    Set docs = CATIA.Documents
    
    ' ouvrir la piece Wireframe_definition.CATPRODUCT, qui contient LotusPoints
    ' lecture du dernier path de WireframeDefinition.CATProduct
    'file_name = ts.ReadLine file_name = CATIA.FileSelectionBox("Select Wireframe definition Product", "*.CATProduct", 0)
    Dim prodDocument As ProductDocument
    Set prodDocument = docs.Open(pathWireframe)
    Dim product1 As Product
    Set product1 = prodDocument.Product
    

    
    ' reperer la pièce LotusPoints.CATPart par recherche dans le produit
    'Dim selection1 As Selection
    'Set selection1 = prodDocument.Selection
    ' pour trouver la sintaxe enregistrer une macro avec l'outil de recherche avancée
    'selection1.Search "CATProductSearch.Part.PartNumber=LotusPoints,all"
    
    ' selection de la pièce
    'Dim part1 As Object 'Part
    'Set part1 = selection1.Item2(1).Value.ReferenceProduct.Parent.Part
    
    'Ouverture directe de LotusPoints puisque c'est chargé avec l'ouverture de WireframeDefinition
    Dim partDocument1 As PartDocument
    Set partDocument1 = docs.Item("LotusPoints.CATPart")
    Dim part1 As Part
    Set part1 = partDocument1.Part
    
    ' maj points suspension avant
    Dim infoAV As Variant
    infoAV = updateLotusPoints(part1, frontNames, frontCoords, "front_points")
    MsgBox "front suspension : maj " & infoAV(0) & ", crée " & infoAV(1)
    
    'maj points suspension arriere
    Dim infoAR As Variant
    infoAR = updateLotusPoints(part1, rearNames, rearCoords, "rear_points")
    MsgBox "rear suspension : maj " & infoAR(0) & ", crée " & infoAR(1)
    
    ' update save and close LotusPoints
    part1.update
    partDocument1.Save
    partDocument1.Close

    
    ' update WireframeDefinition.CATProduct
    product1.update
    prodDocument.Save
    prodDocument.Close
    
    ' update Other Products in update_products
    'Dim prodDocument2 As ProductDocument
    'Dim product2 As Product
    'For i = LBound(update_products) To UBound(update_products)
    '    Set prodDocument2 = docs.Open(update_products(i))                   'il y a une erreur de Byref ici Jean-Michele
    '    Set product2 = prodDocument2.Product
    '    product2.update
    '    prodDocument2.Save
    '    prodDocument2.Close
    'Next

    
    MsgBox "cicabum scatush ts"
    MsgBox "Kung Fu Fiiiiighting"
    

End Sub


Function isInArray(arr As Variant, strItem As Variant) As Boolean
    Dim i As Long
    
    For i = LBound(arr) To UBound(arr)
        If arr(i) = strItem Then
            isInArray = True
            Exit Function
        End If
    Next
End Function

Function updateLotusPoints(part1 As Part, pointNames As Variant, pointCoords As Variant, numb_body As String) As Variant
    Dim nbMaj As Integer
    nbMaj = 0
    Dim nbCre As Integer
    nbCre = 0
    
    ' selection du corps principale
    Dim body1 As Body
    Set body1 = part1.Bodies.Item(numb_body)
    MsgBox body1.Name
    
    ' creer une liste des point deja definis
    Dim pointList As HybridShapes
    Set pointList = body1.HybridShapes
    
   
    Dim oldPointNames() As String
    ReDim oldPointNames(1 To pointList.Count)
    For i = 1 To pointList.Count
        oldPointNames(i) = pointList.Item(i).Name
        'MsgBox oldPointNames(i)
    Next
    
    
    ' variables definition point
    Dim hybridShapeFactory1 As HybridShapeFactory
    Set hybridShapeFactory1 = part1.HybridShapeFactory
    Dim hybridShapePointCoord1 As HybridShapePointCoord
    
    ' accéder aux paramètres des points existants
    Dim parameters1 As Parameters
    Set parameters1 = part1.Parameters
    
    ' modification ou creation des points
    
    Dim name_body As String
    name_body = body1.Name
    For i = LBound(pointNames) To UBound(pointNames)
        
        ' si le point existe deja
        If isInArray(oldPointNames, pointNames(i)) Then
             'maj du point avec les nouvelles cordonnees
            
            'comment inserer le nom de la piece ? Rendre file_name global ?
            ' et faut pouvoir insérer le nom du point dans le path a laide de pointnames aussi
           parameters1.Item("LotusPoints\" & name_body & "\" & pointNames(i) & "\X").Value = pointCoords(i, 0)
           parameters1.Item("LotusPoints\" & name_body & "\" & pointNames(i) & "\Y").Value = -pointCoords(i, 1)
           parameters1.Item("LotusPoints\" & name_body & "\" & pointNames(i) & "\Z").Value = pointCoords(i, 2)
            
           'MsgBox "maj " & pointList.Item(pointNames(i)).Name
           nbMaj = nbMaj + 1
        Else
            'creation du point
            'MsgBox "creation " & pointNames(i)
            Set hybridShapePointCoord1 = hybridShapeFactory1.AddNewPointCoord(pointCoords(i, 0), -pointCoords(i, 1), pointCoords(i, 2)) ' il faut mettre les coors
            hybridShapePointCoord1.Name = pointNames(i)
            ' ajoute le point au corps de LotusPoint
            body1.InsertHybridShape hybridShapePointCoord1
            nbCre = nbCre + 1
        End If
    Next

    ' renvoye le nb de points maj et le nb de points crees
    updateLotusPoints = Array(nbMaj, nbCre)
End Function
